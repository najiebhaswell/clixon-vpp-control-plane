module vpp-bonding {
    yang-version 1.1;
    namespace "http://example.com/vpp/bonding";
    prefix vpp-bond;

    import ietf-yang-types {
        prefix yang;
    }

    organization "Example Organization";
    contact "admin@example.com";
    description
        "YANG module for VPP bonding (LAG/LACP) interface configuration.
         Based on VPP bond_create and bond_enslave APIs.";

    revision 2025-12-12 {
        description "Initial revision for VPP 25.06";
    }

    /*
     * Typedefs
     */
    typedef bond-mode {
        type enumeration {
            enum round-robin {
                value 1;
                description "Round-robin load balancing";
            }
            enum active-backup {
                value 2;
                description "Active-backup (failover)";
            }
            enum xor {
                value 3;
                description "XOR based load balancing";
            }
            enum broadcast {
                value 4;
                description "Broadcast on all slaves";
            }
            enum lacp {
                value 5;
                description "IEEE 802.3ad LACP";
            }
        }
        description "Bond interface mode";
    }

    typedef bond-load-balance {
        type enumeration {
            enum l2 {
                value 0;
                description "Load balance based on L2 (MAC)";
            }
            enum l34 {
                value 1;
                description "Load balance based on L3/L4 (IP/Port)";
            }
            enum l23 {
                value 2;
                description "Load balance based on L2 and L3";
            }
            enum round-robin {
                value 3;
                description "Round-robin (for XOR/LACP modes)";
            }
        }
        description "Load balancing algorithm for XOR and LACP modes";
    }

    typedef lacp-rate {
        type enumeration {
            enum slow {
                value 0;
                description "LACP slow rate (30 seconds)";
            }
            enum fast {
                value 1;
                description "LACP fast rate (1 second)";
            }
        }
        default slow;
        description "LACP PDU transmission rate";
    }

    typedef lacp-state {
        type enumeration {
            enum off {
                value 0;
                description "LACP off";
            }
            enum negotiating {
                value 1;
                description "LACP negotiating";
            }
            enum expired {
                value 2;
                description "LACP expired";
            }
            enum disabled {
                value 3;
                description "LACP disabled on slave";
            }
            enum defaulted {
                value 4;
                description "LACP defaulted";
            }
            enum current {
                value 5;
                description "LACP current (active)";
            }
        }
        description "LACP negotiation state";
    }

    /*
     * Groupings
     */
    grouping lacp-partner-info {
        description "LACP partner (remote) information";
        
        leaf partner-system-id {
            type yang:mac-address;
            description "Partner system MAC address";
        }
        leaf partner-system-priority {
            type uint16;
            description "Partner system priority";
        }
        leaf partner-key {
            type uint16;
            description "Partner aggregation key";
        }
        leaf partner-port-id {
            type uint16;
            description "Partner port ID";
        }
        leaf partner-port-priority {
            type uint16;
            description "Partner port priority";
        }
    }

    grouping lacp-actor-info {
        description "LACP actor (local) information";
        
        leaf actor-system-id {
            type yang:mac-address;
            description "Local system MAC address";
        }
        leaf actor-system-priority {
            type uint16;
            description "Local system priority";
        }
        leaf actor-key {
            type uint16;
            description "Local aggregation key";
        }
        leaf actor-port-id {
            type uint16;
            description "Local port ID";
        }
        leaf actor-port-priority {
            type uint16;
            description "Local port priority";
        }
    }

    /*
     * Configuration Container
     */
    container bonding {
        description "Bond interface configuration";

        list bond-interface {
            key "name";
            description "Bond interface definition";

            leaf name {
                type string {
                    length "1..32";
                    pattern 'BondEthernet[0-9]+';
                }
                description
                    "Bond interface name. Must follow VPP naming convention.
                     Example: BondEthernet0, BondEthernet1";
            }

            leaf instance {
                type uint32;
                description
                    "Bond instance number. If not specified, derived from name.
                     Must be unique across all bond interfaces.";
            }

            leaf mode {
                type bond-mode;
                mandatory true;
                description "Bonding mode";
            }

            leaf load-balance {
                type bond-load-balance;
                default l2;
                description
                    "Load balancing algorithm. Only applicable for
                     XOR and LACP modes.";
            }

            leaf mac-address {
                type yang:mac-address;
                description
                    "MAC address for the bond interface.
                     If not specified, uses first slave's MAC.";
            }

            leaf numa-only {
                type boolean;
                default false;
                description
                    "When true, only use slaves on the same NUMA node
                     for load balancing.";
            }

            /*
             * LACP-specific configuration
             */
            container lacp {
                when "../mode = 'lacp'";
                description "LACP-specific configuration";

                leaf rate {
                    type lacp-rate;
                    default slow;
                    description "LACP PDU transmission rate";
                }

                leaf system-priority {
                    type uint16;
                    default 32768;
                    description "LACP system priority (lower = higher priority)";
                }
            }

            /*
             * Slave interfaces
             */
            list slave {
                key "interface";
                description "Slave interface configuration";

                leaf interface {
                    type string {
                        length "1..64";
                    }
                    description
                        "Slave interface name.
                         Example: GigabitEthernet0/8/0";
                }

                leaf passive {
                    type boolean;
                    default false;
                    description
                        "LACP passive mode. When true, slave does not
                         initiate LACP negotiation (remote must be active).";
                    when "../../mode = 'lacp'";
                }

                leaf long-timeout {
                    type boolean;
                    default false;
                    description
                        "Use long timeout (90s) instead of short (3s)
                         for LACP neighbor expiry.";
                    when "../../mode = 'lacp'";
                }

                leaf port-priority {
                    type uint16;
                    default 32768;
                    description "LACP port priority (lower = higher priority)";
                    when "../../mode = 'lacp'";
                }

                /*
                 * Operational state for this slave
                 */
                container state {
                    config false;
                    description "Slave operational state";

                    leaf sw-if-index {
                        type uint32;
                        description "VPP sw_if_index of slave";
                    }

                    leaf is-active {
                        type boolean;
                        description "Whether slave is actively forwarding";
                    }

                    leaf lacp-state {
                        type lacp-state;
                        description "Current LACP state";
                    }

                    uses lacp-partner-info;
                    uses lacp-actor-info;
                }
            }

            /*
             * Bond operational state
             */
            container state {
                config false;
                description "Bond interface operational state";

                leaf sw-if-index {
                    type uint32;
                    description "VPP sw_if_index of bond";
                }

                leaf active-slaves {
                    type uint32;
                    description "Number of active slave interfaces";
                }

                leaf total-slaves {
                    type uint32;
                    description "Total number of slave interfaces";
                }
            }
        }
    }

    /*
     * RPCs
     */
    rpc bond-create {
        description "Create a new bond interface";
        input {
            leaf mode {
                type bond-mode;
                mandatory true;
            }
            leaf load-balance {
                type bond-load-balance;
                default l2;
            }
            leaf mac-address {
                type yang:mac-address;
            }
            leaf instance {
                type uint32;
                description "Specific instance number (optional)";
            }
        }
        output {
            leaf interface-name {
                type string;
                description "Created interface name";
            }
            leaf sw-if-index {
                type uint32;
                description "VPP sw_if_index";
            }
        }
    }

    rpc bond-delete {
        description "Delete a bond interface";
        input {
            leaf name {
                type string;
                mandatory true;
                description "Bond interface name to delete";
            }
        }
        output {
            leaf result {
                type boolean;
            }
        }
    }

    rpc bond-enslave {
        description "Add a slave interface to a bond";
        input {
            leaf bond-name {
                type string;
                mandatory true;
                description "Bond interface name";
            }
            leaf slave-interface {
                type string;
                mandatory true;
                description "Interface to enslave";
            }
            leaf passive {
                type boolean;
                default false;
            }
            leaf long-timeout {
                type boolean;
                default false;
            }
        }
        output {
            leaf result {
                type boolean;
            }
        }
    }

    rpc bond-detach-slave {
        description "Remove a slave interface from a bond";
        input {
            leaf slave-interface {
                type string;
                mandatory true;
                description "Interface to detach";
            }
        }
        output {
            leaf result {
                type boolean;
            }
        }
    }
}
